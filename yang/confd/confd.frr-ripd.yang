module confd.frr-ripd {
  namespace "urn:dummy";
  prefix "dummy";

  import tailf-common {
    prefix tailf;
  }
  import frr-ripd {
    prefix frr-ripd;
  }

  tailf:annotate-module "frr-ripd" {
    tailf:annotate-statement "container[name='ripd']" {
      tailf:annotate-statement "container[name='state']" {
        tailf:callpoint "state";
      }
    }
    tailf:annotate-statement "rpc[name='clear-rip-route']" {
      tailf:actionpoint "actionpoint";
    }
    tailf:annotate-statement "augment[name='/frr-interface:lib/frr-interface:interface']" {
      tailf:annotate-statement "container[name='rip']" {
        tailf:annotate-statement "container[name='authentication']" {
          tailf:annotate-statement "leaf[name='type']" {
            tailf:annotate-statement "type[name='enumeration']" {
              tailf:annotate-statement "enum[name='none']" {
                tailf:code-name "auth_none";
              }
            }
          }
        }
      }
    }
  }
}
